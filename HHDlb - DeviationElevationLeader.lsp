(defun c:HHDlb (/  p1 p2 x1 y1 z1 z1r x2 y2 z2 z2r d ptcoord textloc)
  (while
    (setq p1 (getpoint "\nPick 1st Point: "))
	(setq p2 (getpoint "\nPick 2nd Point: "))
    (setq textloc (getpoint "\nPick Label Location: "))
    (setq x1 (rtos (car p1) 2 2))
    (setq y1 (rtos (cadr p1) 2 2))
    ;(setq z1 (rtos (caddr p1) 2 2))
	(setq z1 (rtos (caddr p1) 2 3))
	(setq x2 (rtos (car p2) 2 2))
    (setq y2 (rtos (cadr p2) 2 2))
    ;(setq z2 (rtos (caddr p2) 2 2))
	(setq z2 (rtos (caddr p2) 2 3))
	(setq z1r (caddr p1))
	(setq z2r (caddr p2))
	(setq d (rtos(* (- z2r z1r) 1000) 2 0))
	(setq ptcoord (strcat z2 "\n " z1 "\n" d ))
	;(setq ptcoord (strcat z2 "\n " z1  ))
    (command "_LEADER" p1 textloc "" ptcoord "")
  )
)
