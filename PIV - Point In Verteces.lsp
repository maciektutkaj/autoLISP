(defun c:PIV (/ ss B)
(setq B (getreal "\nPodaj wielkosc punktu:"))
(command "_PDmode" 35)
(command "_PDsize" (/ B 2))
 (and
   (setq ss (ssget '((0 . "LWPOLYLINE"))))
   ((lambda (i / l lst)
      (while (setq e (ssname ss (setq i (1+ i))))
        (foreach x (entget e)
          (and (eq 10 (car x))
               (not (member (setq l (list (cadr x) (caddr x) (cdr (assoc 38 (entget e))))) lst))
               (setq lst (cons l lst))
               (entmakex (list '(0 . "Point")
                               '(100 . "AcDbEntity")
                               '(100 . "AcDbPoint")
                               (cons 10 l)
                         )
               )
          )
        )
      )
    )
     -1
   )
 )
 (princ)
)
