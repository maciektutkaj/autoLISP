(defun c:HPD (/  p1 v2 v2r x1 y1 z1 z1r dev devr B hproj hpom txt1p odst1 odst2 odsthpom odstdev devdod)
	(command "_layer" "_m" "!GDX_dH" "_c" "7" """")
	(setq B (getreal "\nPodaj wysokosc tekstu: "))
	(setq v2 (getreal "\nPodaj wartosc projektowa: "))
 (while
    (setq p1 (getpoint "\nWskaz punkt pomierzony: "))
    (setq txt1p (getpoint "\nWskaz lokalizacje tekstu: "))
	(setq x1 (rtos (car p1) 2 2))
    (setq y1 (rtos (cadr p1) 2 2))
	(setq z1r (rtos (caddr p1) 2 3))
	(setq z1 (caddr p1))
	(setq v2r (rtos v2 2 3))
	(setq dev (* (- z1r v2r) 1000))
	(setq hproj (strcat v2r))
	(setq devr (stracat dev))
	(setq hpom (strcat z1r))
	(setq odsthpom (rtos (* (+ B (* B 0.5)) -1)))
	(setq odstdev (rtos (* (* (+ B (* B 0.5)) 2) -1)))
	(setq odst1 (strcat "@0" "," "" odsthpom ""))
	(setq odst2 (strcat "@0" "," "" odstdev ""))
		(if (> (- z1r v2) 0)
			(progn
			(setq devdod (strcat "+" "" dev ""))
			(command "_color" "7")
			(command "_text" txt1p B "0" hproj )
			(command "_color" "1")
			(command "_text" txt1p B "0" hpom )
			(command "._move" (entlast) "" txt1p odst1 )
			(command "_color" "7")
			(command "_text" txt1p B "0" devdod )
			(command "._move" (entlast) "" txt1p odst2 )
			);progn
		);if
		(if (<= (- z1r v2) 0)
		(progn
			(command "_color" "7")
			(command "_text" txt1p B "0" hproj )
			(command "_color" "1")
			(command "_text" txt1p B "0" hpom )
			(command "._move" (entlast) "" txt1p odst1 )
			(command "_color" "7")
			(command "_text" txt1p B "0" dev )
			(command "._move" (entlast) "" txt1p odst2 )	
		);progn
		);if
  )
 )
 (princ "hpd")
