(defun c:plLen  (/ cEnt tStr tBox tHgt tWid gr sPt cPt lAng bPt tPt pt1 pt2 pt3 pt4)
  (vl-load-com)
  (if (and (setq cEnt (car (entsel "\nSelect Object: ")))
           (member (cdr (assoc 0 (entget cEnt)))
                   '("LWPOLYLINE" "POLYLINE" "LINE")))
    (progn
      (setq tStr (rtos (vla-get-length
                         (vlax-ename->vla-object cEnt)))
            tBox (textbox (list (cons 1 tStr) (cons 40 (getvar "TEXTSIZE"))))
            tHgt (- (cadadr tBox) (cadar tBox))
            twid (- (caadr tBox) (caar tBox)))
      (princ "\nWskaz pozycje tekstu : ")
      (while (eq 5 (car (setq gr (grread t 5 0))))
        (redraw)
        (if (listp (setq sPt (cadr gr)))
          (progn
            (setq cPt  (vlax-curve-getClosestPointto cEnt sPt)
                  lAng (angle cPt sPt)
                  bpt  (polar cPt lAng (/ (getvar "TEXTSIZE") 2.))
                  tpt  (polar bpt lAng tHgt)
                  mPt  (polar bPt lAng (/ tHgt 2.))
                  pt1  (polar bpt (+ lAng (/ pi 2.)) (/ tWid 2.))
                  pt2  (polar bPt (- lAng (/ pi 2.)) (/ tWid 2.))
                  pt3  (polar tpt (+ lAng (/ pi 2.)) (/ tWid 2.))
                  pt4  (polar tPt (- lAng (/ pi 2.)) (/ tWid 2.)))
            (grvecs (list -3 pt1 pt2 pt3 pt4 pt1 pt3 pt2 pt4)))))
      (if (eq 3 (car gr))
        (progn
          (setq lAng (- lAng (/ pi 2.)))
          (cond ((and (> lAng (/ pi 2)) (<= lAng pi))
                 (setq lAng (- lAng pi)))
                ((and (> lAng pi) (<= lAng (/ (* 3 pi) 2)))
                 (setq lAng (+ lAng pi))))
          (Make_Text mPt tStr lAng))))
    (princ "\n<!> Incorrect Selection <!>"))
  (redraw)
  (princ))

(defun Make_Text  (pt val rot)
  (entmake
    (list
      (cons 0 "TEXT")
      (cons 8 (getvar "CLAYER"))
      (cons 62 2)
      (cons 10 pt)
      (cons 40 (getvar "TEXTSIZE"))
      (cons 1 val)
      (cons 50 rot)
      (cons 7 (getvar "TEXTSTYLE"))
      (cons 71 0)
      (cons 72 1)
      (cons 73 2)
      (cons 11 pt))))
(prompt "\nKOMENDA -> PlLen")
